// Source file companion for @turbine-engine/front-compression-hub
// represents: geometry/Front Compression Hub - JET v3.stl
// role: represents
// This file does not replace any child package.
import Systems::*;

package FrontCompressionHubJETV3 {
    part def FrontCompressionHubJETV3 :> Part;
}
