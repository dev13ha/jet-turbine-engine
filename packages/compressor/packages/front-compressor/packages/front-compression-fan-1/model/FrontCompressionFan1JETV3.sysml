// Source file companion for @turbine-engine/front-compression-fan-1
// represents: geometry/Front Compression Fan-1- JET v3.stl
// role: represents
// This file does not replace any child package.
import Systems::*;

package FrontCompressionFan1JETV3 {
    part def FrontCompressionFan1JETV3 :> Part;
}
