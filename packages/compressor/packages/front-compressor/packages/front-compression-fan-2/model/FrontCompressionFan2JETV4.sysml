// Source file companion for @turbine-engine/front-compression-fan-2
// represents: geometry/Front Compression Fan-2- JET v4.stl
// role: represents
// This file does not replace any child package.
import Systems::*;

package FrontCompressionFan2JETV4 {
    part def FrontCompressionFan2JETV4 :> Part;
}
