// @turbine-engine/front-compression-fan-2 1.0.0
// represents this package. Child part usages are contains, not dependsOn.
// Placement, mates, materials, and behavior parameters are UNKNOWN.
import Systems::*;

package FrontCompressionFan2 {
    part def FrontCompressionFan2 :> Part;
}
