// Source file companion for @turbine-engine/front-compression-fan-4
// represents: geometry/Front Compression Fan-4- JET v4.stl
// role: represents
// This file does not replace any child package.
import Systems::*;

package FrontCompressionFan4JETV4 {
    part def FrontCompressionFan4JETV4 :> Part;
}
