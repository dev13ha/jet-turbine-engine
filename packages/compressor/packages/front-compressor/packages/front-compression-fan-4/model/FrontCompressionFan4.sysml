// @turbine-engine/front-compression-fan-4 1.0.0
// represents this package. Child part usages are contains, not dependsOn.
// Placement, mates, materials, and behavior parameters are UNKNOWN.
import Systems::*;

package FrontCompressionFan4 {
    part def FrontCompressionFan4 :> Part;
}
