// Source file companion for @turbine-engine/front-compression-fan-3
// represents: geometry/Front Compression Fan-3- JET v4.stl
// role: represents
// This file does not replace any child package.
import Systems::*;

package FrontCompressionFan3JETV4 {
    part def FrontCompressionFan3JETV4 :> Part;
}
