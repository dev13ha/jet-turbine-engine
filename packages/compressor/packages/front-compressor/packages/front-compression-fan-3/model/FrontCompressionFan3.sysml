// @turbine-engine/front-compression-fan-3 1.0.0
// represents this package. Child part usages are contains, not dependsOn.
// Placement, mates, materials, and behavior parameters are UNKNOWN.
import Systems::*;

package FrontCompressionFan3 {
    part def FrontCompressionFan3 :> Part;
}
