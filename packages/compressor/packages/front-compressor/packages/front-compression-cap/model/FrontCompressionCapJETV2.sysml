// Source file companion for @turbine-engine/front-compression-cap
// represents: geometry/Front Compression Cap- JET v2.stl
// role: represents
// This file does not replace any child package.
import Systems::*;

package FrontCompressionCapJETV2 {
    part def FrontCompressionCapJETV2 :> Part;
}
