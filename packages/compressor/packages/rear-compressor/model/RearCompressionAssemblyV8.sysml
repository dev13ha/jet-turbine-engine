// Source file companion for @turbine-engine/rear-compressor
// derivedFrom: geometry/Rear Compression Assembly v8.stl
// role: assembly-reference
// This file does not replace any child package.
import Systems::*;

package RearCompressionAssemblyV8 {
    part def RearCompressionAssemblyV8 :> Part;
}
