// Source file companion for @turbine-engine/rear-compression-fan-1
// represents: geometry/Rear Compression Fan-1- JET v5.stl
// role: represents
// This file does not replace any child package.
import Systems::*;

package RearCompressionFan1JETV5 {
    part def RearCompressionFan1JETV5 :> Part;
}
