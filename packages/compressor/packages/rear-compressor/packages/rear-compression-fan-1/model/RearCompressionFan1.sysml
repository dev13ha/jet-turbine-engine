// @turbine-engine/rear-compression-fan-1 1.0.0
// represents this package. Child part usages are contains, not dependsOn.
// Placement, mates, materials, and behavior parameters are UNKNOWN.
import Systems::*;

package RearCompressionFan1 {
    part def RearCompressionFan1 :> Part;
}
