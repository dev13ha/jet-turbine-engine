// Source file companion for @turbine-engine/rear-compression-fan-2
// represents: geometry/Rear Compression Fan-2- JET v6.stl
// role: represents
// This file does not replace any child package.
import Systems::*;

package RearCompressionFan2JETV6 {
    part def RearCompressionFan2JETV6 :> Part;
}
