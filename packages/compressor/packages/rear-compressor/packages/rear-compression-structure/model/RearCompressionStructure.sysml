// @turbine-engine/rear-compression-structure 1.0.0
// represents this package. Child part usages are contains, not dependsOn.
// Placement, mates, materials, and behavior parameters are UNKNOWN.
import Systems::*;

package RearCompressionStructure {
    part def RearCompressionStructure :> Part;
}
