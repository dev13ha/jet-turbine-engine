// Source file companion for @turbine-engine/rear-compression-structure
// represents: geometry/Rear Compression Structure - JET v2.stl
// role: represents
// This file does not replace any child package.
import Systems::*;

package RearCompressionStructureJETV2 {
    part def RearCompressionStructureJETV2 :> Part;
}
