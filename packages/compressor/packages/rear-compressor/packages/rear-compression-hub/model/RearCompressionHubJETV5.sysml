// Source file companion for @turbine-engine/rear-compression-hub
// represents: geometry/Rear Compression Hub - JET v5.stl
// role: represents
// This file does not replace any child package.
import Systems::*;

package RearCompressionHubJETV5 {
    part def RearCompressionHubJETV5 :> Part;
}
