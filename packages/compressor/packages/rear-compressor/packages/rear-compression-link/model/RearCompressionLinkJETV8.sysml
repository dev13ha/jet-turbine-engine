// Source file companion for @turbine-engine/rear-compression-link
// represents: geometry/Rear Compression Link - JET v8.stl
// role: represents
// This file does not replace any child package.
import Systems::*;

package RearCompressionLinkJETV8 {
    part def RearCompressionLinkJETV8 :> Part;
}
