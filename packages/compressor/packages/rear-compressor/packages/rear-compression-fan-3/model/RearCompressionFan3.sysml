// @turbine-engine/rear-compression-fan-3 1.0.0
// represents this package. Child part usages are contains, not dependsOn.
// Placement, mates, materials, and behavior parameters are UNKNOWN.
import Systems::*;

package RearCompressionFan3 {
    part def RearCompressionFan3 :> Part;
}
