// Source file companion for @turbine-engine/rear-compression-fan-3
// represents: geometry/Rear Compression Fan-3- JET v9.stl
// role: represents
// This file does not replace any child package.
import Systems::*;

package RearCompressionFan3JETV9 {
    part def RearCompressionFan3JETV9 :> Part;
}
