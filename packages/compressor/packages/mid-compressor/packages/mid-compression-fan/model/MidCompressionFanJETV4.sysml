// Source file companion for @turbine-engine/mid-compression-fan
// represents: geometry/Mid Compression Fan - JET v4.stl
// role: represents
// This file does not replace any child package.
import Systems::*;

package MidCompressionFanJETV4 {
    part def MidCompressionFanJETV4 :> Part;
}
