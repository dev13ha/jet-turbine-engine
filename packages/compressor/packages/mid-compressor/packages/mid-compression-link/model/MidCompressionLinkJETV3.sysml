// Source file companion for @turbine-engine/mid-compression-link
// represents: geometry/Mid Compression Link - JET v3.stl
// role: represents
// This file does not replace any child package.
import Systems::*;

package MidCompressionLinkJETV3 {
    part def MidCompressionLinkJETV3 :> Part;
}
