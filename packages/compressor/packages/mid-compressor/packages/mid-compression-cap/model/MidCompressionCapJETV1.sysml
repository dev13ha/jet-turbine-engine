// Source file companion for @turbine-engine/mid-compression-cap
// represents: geometry/Mid Compression Cap - JET v1.stl
// role: represents
// This file does not replace any child package.
import Systems::*;

package MidCompressionCapJETV1 {
    part def MidCompressionCapJETV1 :> Part;
}
