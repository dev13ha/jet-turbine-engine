// Source file companion for @turbine-engine/mid-axis-cover
// represents: geometry/Mid Axis Cover - JET v2.stl
// role: represents
// This file does not replace any child package.
import Systems::*;

package MidAxisCoverJETV2 {
    part def MidAxisCoverJETV2 :> Part;
}
