// Source file companion for @turbine-engine/mid-compression-shaft
// represents: geometry/Mid Compression Shaft- JET v3.stl
// role: represents
// This file does not replace any child package.
import Systems::*;

package MidCompressionShaftJETV3 {
    part def MidCompressionShaftJETV3 :> Part;
}
