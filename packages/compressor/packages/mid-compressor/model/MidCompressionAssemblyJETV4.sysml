// Source file companion for @turbine-engine/mid-compressor
// derivedFrom: geometry/Mid Compression Assembly - JET v4.stl
// role: assembly-reference
// This file does not replace any child package.
import Systems::*;

package MidCompressionAssemblyJETV4 {
    part def MidCompressionAssemblyJETV4 :> Part;
}
