// Source file companion for @turbine-engine/turbine
// derivedFrom: geometry/Turbine Assembly- JET v9.stl
// role: assembly-reference
// This file does not replace any child package.
import Systems::*;

package TurbineAssemblyJETV9 {
    part def TurbineAssemblyJETV9 :> Part;
}
