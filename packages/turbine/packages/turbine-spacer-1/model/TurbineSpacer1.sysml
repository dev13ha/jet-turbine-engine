// @turbine-engine/turbine-spacer-1 1.0.0
// represents this package. Child part usages are contains, not dependsOn.
// Placement, mates, materials, and behavior parameters are UNKNOWN.
import Systems::*;

package TurbineSpacer1 {
    part def TurbineSpacer1 :> Part;
}
