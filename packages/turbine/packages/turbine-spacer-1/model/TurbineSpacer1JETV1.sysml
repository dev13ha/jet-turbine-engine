// Source file companion for @turbine-engine/turbine-spacer-1
// represents: geometry/Turbine Spacer- 1 - JET v1.stl
// role: represents
// This file does not replace any child package.
import Systems::*;

package TurbineSpacer1JETV1 {
    part def TurbineSpacer1JETV1 :> Part;
}
