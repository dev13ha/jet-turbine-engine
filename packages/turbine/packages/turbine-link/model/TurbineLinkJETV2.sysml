// Source file companion for @turbine-engine/turbine-link
// represents: geometry/Turbine Link- JET v2.stl
// role: represents
// This file does not replace any child package.
import Systems::*;

package TurbineLinkJETV2 {
    part def TurbineLinkJETV2 :> Part;
}
