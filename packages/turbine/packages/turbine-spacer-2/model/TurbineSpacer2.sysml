// @turbine-engine/turbine-spacer-2 1.0.0
// represents this package. Child part usages are contains, not dependsOn.
// Placement, mates, materials, and behavior parameters are UNKNOWN.
import Systems::*;

package TurbineSpacer2 {
    part def TurbineSpacer2 :> Part;
}
