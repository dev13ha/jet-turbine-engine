// Source file companion for @turbine-engine/turbine-spacer-2
// represents: geometry/Turbine Spacer-2 -JET v1.stl
// role: represents
// This file does not replace any child package.
import Systems::*;

package TurbineSpacer2JETV1 {
    part def TurbineSpacer2JETV1 :> Part;
}
