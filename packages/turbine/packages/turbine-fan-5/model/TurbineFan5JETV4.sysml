// Source file companion for @turbine-engine/turbine-fan-5
// represents: geometry/Turbine Fan-5- JET v4.stl
// role: represents
// This file does not replace any child package.
import Systems::*;

package TurbineFan5JETV4 {
    part def TurbineFan5JETV4 :> Part;
}
