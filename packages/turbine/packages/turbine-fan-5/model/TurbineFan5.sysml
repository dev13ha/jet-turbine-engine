// @turbine-engine/turbine-fan-5 1.0.0
// represents this package. Child part usages are contains, not dependsOn.
// Placement, mates, materials, and behavior parameters are UNKNOWN.
import Systems::*;

package TurbineFan5 {
    part def TurbineFan5 :> Part;
}
