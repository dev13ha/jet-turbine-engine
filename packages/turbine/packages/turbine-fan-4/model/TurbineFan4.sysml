// @turbine-engine/turbine-fan-4 1.0.0
// represents this package. Child part usages are contains, not dependsOn.
// Placement, mates, materials, and behavior parameters are UNKNOWN.
import Systems::*;

package TurbineFan4 {
    part def TurbineFan4 :> Part;
}
