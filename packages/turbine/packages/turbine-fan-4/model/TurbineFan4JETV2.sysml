// Source file companion for @turbine-engine/turbine-fan-4
// represents: geometry/Turbine Fan-4- JET v2.stl
// role: represents
// This file does not replace any child package.
import Systems::*;

package TurbineFan4JETV2 {
    part def TurbineFan4JETV2 :> Part;
}
