// @turbine-engine/turbine-fan-3 1.0.0
// represents this package. Child part usages are contains, not dependsOn.
// Placement, mates, materials, and behavior parameters are UNKNOWN.
import Systems::*;

package TurbineFan3 {
    part def TurbineFan3 :> Part;
}
