// Source file companion for @turbine-engine/turbine-fan-3
// represents: geometry/Turbine Fan-3- JET v5.stl
// role: represents
// This file does not replace any child package.
import Systems::*;

package TurbineFan3JETV5 {
    part def TurbineFan3JETV5 :> Part;
}
