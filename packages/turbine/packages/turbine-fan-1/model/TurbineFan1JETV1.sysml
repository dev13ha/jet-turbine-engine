// Source file companion for @turbine-engine/turbine-fan-1
// represents: geometry/Turbine Fan-1- JET v1.stl
// role: represents
// This file does not replace any child package.
import Systems::*;

package TurbineFan1JETV1 {
    part def TurbineFan1JETV1 :> Part;
}
