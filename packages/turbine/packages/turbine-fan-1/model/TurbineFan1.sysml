// @turbine-engine/turbine-fan-1 1.0.0
// represents this package. Child part usages are contains, not dependsOn.
// Placement, mates, materials, and behavior parameters are UNKNOWN.
import Systems::*;

package TurbineFan1 {
    part def TurbineFan1 :> Part;
}
