// Source file companion for @turbine-engine/turbine-housing
// represents: geometry/Turbine Housing- JET v3.stl
// role: represents
// This file does not replace any child package.
import Systems::*;

package TurbineHousingJETV3 {
    part def TurbineHousingJETV3 :> Part;
}
