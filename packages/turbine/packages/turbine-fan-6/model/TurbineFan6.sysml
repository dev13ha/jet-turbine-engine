// @turbine-engine/turbine-fan-6 1.0.0
// represents this package. Child part usages are contains, not dependsOn.
// Placement, mates, materials, and behavior parameters are UNKNOWN.
import Systems::*;

package TurbineFan6 {
    part def TurbineFan6 :> Part;
}
