// Source file companion for @turbine-engine/turbine-fan-6
// represents: geometry/Turbine Fan-6- JET v2.stl
// role: represents
// This file does not replace any child package.
import Systems::*;

package TurbineFan6JETV2 {
    part def TurbineFan6JETV2 :> Part;
}
