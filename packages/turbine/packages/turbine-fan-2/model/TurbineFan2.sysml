// @turbine-engine/turbine-fan-2 1.0.0
// represents this package. Child part usages are contains, not dependsOn.
// Placement, mates, materials, and behavior parameters are UNKNOWN.
import Systems::*;

package TurbineFan2 {
    part def TurbineFan2 :> Part;
}
