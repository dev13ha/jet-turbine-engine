// Source file companion for @turbine-engine/turbine-fan-2
// represents: geometry/Turbine Fan-2- JET v5.stl
// role: represents
// This file does not replace any child package.
import Systems::*;

package TurbineFan2JETV5 {
    part def TurbineFan2JETV5 :> Part;
}
