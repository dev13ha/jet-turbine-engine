// Source file companion for @turbine-engine/turbine-shaft
// represents: geometry/Turbine Shaft- JET v3.stl
// role: represents
// This file does not replace any child package.
import Systems::*;

package TurbineShaftJETV3 {
    part def TurbineShaftJETV3 :> Part;
}
