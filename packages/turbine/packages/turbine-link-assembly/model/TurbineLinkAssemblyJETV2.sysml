// Source file companion for @turbine-engine/turbine-link-assembly
// represents: geometry/Turbine Link Assembly- JET v2.stl
// role: represents
// This file does not replace any child package.
import Systems::*;

package TurbineLinkAssemblyJETV2 {
    part def TurbineLinkAssemblyJETV2 :> Part;
}
