// @turbine-engine/turbine-link-assembly 1.0.0
// represents this package. Child part usages are contains, not dependsOn.
// Placement, mates, materials, and behavior parameters are UNKNOWN.
import Systems::*;

package TurbineLinkAssembly {
    part def TurbineLinkAssembly :> Part;
}
