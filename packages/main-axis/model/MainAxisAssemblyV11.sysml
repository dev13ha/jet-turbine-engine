// Source file companion for @turbine-engine/main-axis
// derivedFrom: geometry/Main Axis Assembly v11.stl
// role: assembly-reference
// This file does not replace any child package.
import Systems::*;

package MainAxisAssemblyV11 {
    part def MainAxisAssemblyV11 :> Part;
}
