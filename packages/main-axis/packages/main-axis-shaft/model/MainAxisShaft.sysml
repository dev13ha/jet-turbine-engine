// @turbine-engine/main-axis-shaft 1.0.0
// represents this package. Child part usages are contains, not dependsOn.
// Placement, mates, materials, and behavior parameters are UNKNOWN.
import Systems::*;

package MainAxisShaft {
    part def MainAxisShaft :> Part;
}
