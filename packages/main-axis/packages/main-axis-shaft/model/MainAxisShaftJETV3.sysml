// Source file companion for @turbine-engine/main-axis-shaft
// represents: geometry/Main Axis Shaft- JET v3.stl
// role: represents
// This file does not replace any child package.
import Systems::*;

package MainAxisShaftJETV3 {
    part def MainAxisShaftJETV3 :> Part;
}
