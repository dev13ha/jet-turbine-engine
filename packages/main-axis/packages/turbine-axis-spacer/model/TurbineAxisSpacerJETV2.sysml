// Source file companion for @turbine-engine/turbine-axis-spacer
// represents: geometry/Turbine Axis Spacer- JET v2.stl
// role: represents
// This file does not replace any child package.
import Systems::*;

package TurbineAxisSpacerJETV2 {
    part def TurbineAxisSpacerJETV2 :> Part;
}
