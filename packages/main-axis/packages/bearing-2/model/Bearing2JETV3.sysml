// Source file companion for @turbine-engine/bearing-2
// represents: geometry/Bearing 2- JET v3.stl
// role: represents
// This file does not replace any child package.
import Systems::*;

package Bearing2JETV3 {
    part def Bearing2JETV3 :> Part;
}
