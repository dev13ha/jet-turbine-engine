// Source file companion for @turbine-engine/bearing-1
// represents: geometry/Bearing- JET v3.stl
// role: represents
// This file does not replace any child package.
import Systems::*;

package BearingJETV3 {
    part def BearingJETV3 :> Part;
}
