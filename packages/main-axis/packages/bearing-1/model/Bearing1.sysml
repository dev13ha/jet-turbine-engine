// @turbine-engine/bearing-1 1.0.0
// represents this package. Child part usages are contains, not dependsOn.
// Placement, mates, materials, and behavior parameters are UNKNOWN.
import Systems::*;

package Bearing1 {
    part def Bearing1 :> Part;
}
