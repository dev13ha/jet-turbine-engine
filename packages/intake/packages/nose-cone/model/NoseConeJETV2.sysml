// Source file companion for @turbine-engine/nose-cone
// represents: geometry/Nose Cone - JET v2.stl
// role: represents
// This file does not replace any child package.
import Systems::*;

package NoseConeJETV2 {
    part def NoseConeJETV2 :> Part;
}
