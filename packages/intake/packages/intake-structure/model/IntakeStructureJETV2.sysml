// Source file companion for @turbine-engine/intake-structure
// represents: geometry/Intake Structure - JET v2.stl
// role: represents
// This file does not replace any child package.
import Systems::*;

package IntakeStructureJETV2 {
    part def IntakeStructureJETV2 :> Part;
}
