// Source file companion for @turbine-engine/intake-fan
// represents: geometry/Intake Fan- JET v2.stl
// role: represents
// This file does not replace any child package.
import Systems::*;

package IntakeFanJETV2 {
    part def IntakeFanJETV2 :> Part;
}
