// Source file companion for @turbine-engine/intake-casing
// represents: geometry/Intake Casing - JET v3.stl
// role: represents
// This file does not replace any child package.
import Systems::*;

package IntakeCasingJETV3 {
    part def IntakeCasingJETV3 :> Part;
}
