// Source file companion for @turbine-engine/core-plate
// represents: geometry/Core Plate- JET v1.stl
// role: represents
// This file does not replace any child package.
import Systems::*;

package CorePlateJETV1 {
    part def CorePlateJETV1 :> Part;
}
