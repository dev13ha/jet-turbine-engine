// Source file companion for @turbine-engine/rear-casing
// represents: geometry/Rear Casing - JET v20.stl
// role: represents
// This file does not replace any child package.
import Systems::*;

package RearCasingJETV20 {
    part def RearCasingJETV20 :> Part;
}
