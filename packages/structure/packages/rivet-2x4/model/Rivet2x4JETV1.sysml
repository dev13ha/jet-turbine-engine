// Source file companion for @turbine-engine/rivet-2x4
// represents: geometry/Rivet 2x4 -JET v1.stl
// role: represents
// This file does not replace any child package.
import Systems::*;

package Rivet2x4JETV1 {
    part def Rivet2x4JETV1 :> Part;
}
