// @turbine-engine/rivet-2x4 1.0.0
// represents this package. Child part usages are contains, not dependsOn.
// Placement, mates, materials, and behavior parameters are UNKNOWN.
import Systems::*;

package Rivet2x4 {
    part def Rivet2x4 :> Part;
}
