// Source file companion for @turbine-engine/heat-ring
// represents: geometry/Heat Ring- JET v1.stl
// role: represents
// This file does not replace any child package.
import Systems::*;

package HeatRingJETV1 {
    part def HeatRingJETV1 :> Part;
}
