// Source file companion for @turbine-engine/combustion-system
// derivedFrom: geometry/Combustion Chamber Assembly- JET v4.stl
// role: assembly-reference
// This file does not replace any child package.
import Systems::*;

package CombustionChamberAssemblyJETV4 {
    part def CombustionChamberAssemblyJETV4 :> Part;
}
