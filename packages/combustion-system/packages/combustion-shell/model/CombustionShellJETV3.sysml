// Source file companion for @turbine-engine/combustion-shell
// represents: geometry/Combustion Shell- JET v3.stl
// role: represents
// This file does not replace any child package.
import Systems::*;

package CombustionShellJETV3 {
    part def CombustionShellJETV3 :> Part;
}
