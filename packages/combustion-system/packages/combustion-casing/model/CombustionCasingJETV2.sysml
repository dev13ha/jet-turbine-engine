// Source file companion for @turbine-engine/combustion-casing
// represents: geometry/Combustion Casing - JET v2.stl
// role: represents
// This file does not replace any child package.
import Systems::*;

package CombustionCasingJETV2 {
    part def CombustionCasingJETV2 :> Part;
}
