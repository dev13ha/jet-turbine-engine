// Source file companion for @turbine-engine/combustion-chamber
// represents: geometry/Combustion Chamber - JET v3.stl
// role: represents
// This file does not replace any child package.
import Systems::*;

package CombustionChamberJETV3 {
    part def CombustionChamberJETV3 :> Part;
}
