// Source file companion for @turbine-engine/combustion-stage
// represents: geometry/Combustion Stage - JET v6.stl
// role: represents
// This file does not replace any child package.
import Systems::*;

package CombustionStageJETV6 {
    part def CombustionStageJETV6 :> Part;
}
