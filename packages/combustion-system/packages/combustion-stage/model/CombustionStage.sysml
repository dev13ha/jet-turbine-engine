// @turbine-engine/combustion-stage 1.0.0
// represents this package. Child part usages are contains, not dependsOn.
// Placement, mates, materials, and behavior parameters are UNKNOWN.
import Systems::*;

package CombustionStage {
    part def CombustionStage :> Part;
}
