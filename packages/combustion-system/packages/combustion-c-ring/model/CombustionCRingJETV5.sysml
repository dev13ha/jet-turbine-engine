// Source file companion for @turbine-engine/combustion-c-ring
// represents: geometry/Combustion C Ring- JET v5.stl
// role: represents
// This file does not replace any child package.
import Systems::*;

package CombustionCRingJETV5 {
    part def CombustionCRingJETV5 :> Part;
}
