// @turbine-engine/fuel-port-cap 1.0.0
// represents this package. Child part usages are contains, not dependsOn.
// Placement, mates, materials, and behavior parameters are UNKNOWN.
import Systems::*;

package FuelPortCap {
    part def FuelPortCap :> Part;
}
