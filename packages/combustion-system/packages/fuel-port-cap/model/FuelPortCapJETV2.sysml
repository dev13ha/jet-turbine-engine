// Source file companion for @turbine-engine/fuel-port-cap
// represents: geometry/Fuel Port Cap - JET v2.stl
// role: represents
// This file does not replace any child package.
import Systems::*;

package FuelPortCapJETV2 {
    part def FuelPortCapJETV2 :> Part;
}
