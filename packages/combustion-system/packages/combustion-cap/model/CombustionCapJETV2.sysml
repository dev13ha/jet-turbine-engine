// Source file companion for @turbine-engine/combustion-cap
// represents: geometry/Combustion Cap- JET v2.stl
// role: represents
// This file does not replace any child package.
import Systems::*;

package CombustionCapJETV2 {
    part def CombustionCapJETV2 :> Part;
}
