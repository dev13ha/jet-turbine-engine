// Source file companion for @turbine-engine/flare-base
// represents: geometry/Flare Base JET v1.stl
// role: represents
// This file does not replace any child package.
import Systems::*;

package FlareBaseJETV1 {
    part def FlareBaseJETV1 :> Part;
}
