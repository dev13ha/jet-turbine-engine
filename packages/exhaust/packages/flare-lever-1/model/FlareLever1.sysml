// @turbine-engine/flare-lever-1 1.0.0
// represents this package. Child part usages are contains, not dependsOn.
// Placement, mates, materials, and behavior parameters are UNKNOWN.
import Systems::*;

package FlareLever1 {
    part def FlareLever1 :> Part;
}
