// Source file companion for @turbine-engine/flare-lever-1
// represents: geometry/Flare Lever-1 - JET v1.stl
// role: represents
// This file does not replace any child package.
import Systems::*;

package FlareLever1JETV1 {
    part def FlareLever1JETV1 :> Part;
}
