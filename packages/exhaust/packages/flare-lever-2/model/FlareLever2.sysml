// @turbine-engine/flare-lever-2 1.0.0
// represents this package. Child part usages are contains, not dependsOn.
// Placement, mates, materials, and behavior parameters are UNKNOWN.
import Systems::*;

package FlareLever2 {
    part def FlareLever2 :> Part;
}
