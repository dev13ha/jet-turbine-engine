// Source file companion for @turbine-engine/flare-lever-2
// represents: geometry/Flare Lever-2 - JET v1.stl
// role: represents
// This file does not replace any child package.
import Systems::*;

package FlareLever2JETV1 {
    part def FlareLever2JETV1 :> Part;
}
