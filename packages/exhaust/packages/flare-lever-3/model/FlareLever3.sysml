// @turbine-engine/flare-lever-3 1.0.0
// represents this package. Child part usages are contains, not dependsOn.
// Placement, mates, materials, and behavior parameters are UNKNOWN.
import Systems::*;

package FlareLever3 {
    part def FlareLever3 :> Part;
}
