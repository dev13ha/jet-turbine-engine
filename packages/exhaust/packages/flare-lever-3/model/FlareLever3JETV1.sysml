// Source file companion for @turbine-engine/flare-lever-3
// represents: geometry/Flare Lever-3 - JET v1.stl
// role: represents
// This file does not replace any child package.
import Systems::*;

package FlareLever3JETV1 {
    part def FlareLever3JETV1 :> Part;
}
