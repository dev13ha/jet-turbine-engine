// Unassigned source file. Not a member of @turbine-engine/turbine-engine.
// Not Core Plate- JET v1.stl. The requested Cone - JET v2.stl is not in the dataset. Not treated as the nose cone.
import Systems::*;

package CoreJETV2 {
    part def CoreJETV2 :> Part;
}
