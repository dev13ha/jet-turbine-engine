// Unassigned source file. Not a member of @turbine-engine/turbine-engine.
// Filename does not match any requested package. Not assigned to a fan.
import Systems::*;

package Blade2JETV7 {
    part def Blade2JETV7 :> Part;
}
