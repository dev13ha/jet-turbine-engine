// Holding package for dataset files that were not assigned to @turbine-engine/turbine-engine.
// Each source file has its own model. These parts are not an assembly.
import Systems::*;

package UnassignedSource {
    part def UnassignedSource :> Part;
}
