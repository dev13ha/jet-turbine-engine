// Unassigned source file. Not a member of @turbine-engine/turbine-engine.
// No rear-turbine-hub package was requested. Not treated as the rear compression hub.
import Systems::*;

package RearTurbineHubJETV2 {
    part def RearTurbineHubJETV2 :> Part;
}
