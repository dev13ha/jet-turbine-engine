// Unassigned source file. Not a member of @turbine-engine/turbine-engine.
// No front-turbine-hub package was requested. Not treated as the front compression hub.
import Systems::*;

package FrontTurbineHubJETV2 {
    part def FrontTurbineHubJETV2 :> Part;
}
