// Unassigned source file. Not a member of @turbine-engine/turbine-engine.
// Filename does not match any requested package. Not assigned to a fan.
import Systems::*;

package Blade1JETV2 {
    part def Blade1JETV2 :> Part;
}
