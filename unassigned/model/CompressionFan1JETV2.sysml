// Unassigned source file. Not a member of @turbine-engine/turbine-engine.
// Distinct from Front Compression Fan-1. No requested package matches this name.
import Systems::*;

package CompressionFan1JETV2 {
    part def CompressionFan1JETV2 :> Part;
}
