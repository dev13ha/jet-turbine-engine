// Source file companion for @turbine-engine/turbine-engine
// derivedFrom: geometry/reference/Open.skp
// role: sketchup-reference
// This file does not replace any child package.
import Systems::*;

package Open {
    part def Open :> Part;
}
