// Source file companion for @turbine-engine/turbine-engine
// derivedFrom: geometry/reference/Working.stl
// role: engine-reference
// This file does not replace any child package.
import Systems::*;

package Working {
    part def Working :> Part;
}
